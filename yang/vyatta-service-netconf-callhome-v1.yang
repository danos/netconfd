module vyatta-service-netconf-callhome-v1 {
	namespace "urn:vyatta.com:mgmt:vyatta-service-netconf-callhome:1";
	prefix service-netconf-callhome;

	import vyatta-types-v1 {
		prefix types;
	}
	import vyatta-services-v1 {
		prefix service;
	}
	import vyatta-service-netconf-v1 {
		prefix netconf;
	}
	import configd-v1 {
		prefix configd;
	}

	organization "AT&T Inc.";
	contact
		"AT&T
		 Postal: 208 S. Akard Street
		         Dallas, TX 75202
		 Web: www.att.com";

	description
		"Copyright (c) 2019, AT&T Intellectual Property.
		 All rights reserved.

		 Copyright (c) 2015-2016 by Brocade Communications Systems, Inc.
		 All rights reserved.

		 Redistribution and use in source and binary forms, with or without
		 modification, are permitted provided that the following conditions
		 are met:

		 1. Redistributions of source code must retain the above copyright
		    notice, this list of conditions and the following disclaimer.
		 2. Redistributions in binary form must reproduce the above
		    copyright notice, this list of conditions and the following
		    disclaimer in the documentation and/or other materials provided
		    with the distribution.
		 3. Neither the name of the copyright holder nor the names of its
		    contributors may be used to endorse or promote products derived
		    from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		 Call-home allows for a device to initiate a secure connection with
		 configured remote management system(s) for additional
		 configuration or simply to register its presence.";

	revision 2015-11-26 {
		description "Initial release of v1.";
	}

	augment /service:service/netconf:netconf {
		configd:end "/opt/vyatta/share/tmplscripts/service/netconf/callhome_end.sh";
		container call-home {
			description "Configure call-home service";
			configd:help "Configure call-home service";
			list netconf-client {
				key host;
				configd:help "List of NETCONF clients";
				description "List of NETCONF clients the NETCONF server is to initiate SSH call-home connections to.";
				leaf host {
					type types:host {
						configd:help "Client IP address or host name";
					}
					description "Client IP address or host name";
				}
				leaf port {
					type types:port;
					default 7777;
					description "IP port for client";
					configd:help "IP port for client";
				}
				leaf disable {
					type empty;
					description "Disable client";
					configd:help "Disable client";
				}
			}
		}
		leaf call-home-status {
			config false;
			type enumeration {
				enum "failed";
				enum "succeeded";
				enum "started";
				enum "not-started";
				enum "unknown";
			}
			description "Status of the call-home operation";
			configd:help "Status of the call-home operation";
			configd:get-state "/usr/sbin/chclient -g";
		}
	}
}
